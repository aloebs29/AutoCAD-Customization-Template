;;
;;	HelloCustomLisp
;;	Author: Andrew Loebs
;;	Desc: Writing hello to the editor using the LISP function
;;			defined in our LispFunctionTemplate
;;
(defun c:HelloCustomLisp ()
	(HelloLispFunction "testing")
)
